# Requirements PET Integration
This document outlines the requirements for developing PET processing and analysis capabilities within Brainstorm. The Brainstorm extension for PET will support importing, processing, registering, visualizing, and analyzing PET data within Brainstorm. 
It will be designed to facilitate the analysis of multimodal neuroimaging data by allowing the user to co-analyze MEG, PET and MRI-derived data. 
PET will be added as a new data type within Brainstorm and will include PET-specific functions for pre-processing and processing.

## #3: Functional Requirements (Container)

### #8: Import PET (Container)

#### #9: Overview (Informational)
A dedicated function for importing PET volumes, based on import_mri.
The import PET functions will include functionalities for:
- file selection via GUI
- format conversions (DICOM, NIFTI etc.)
- naming the imported PET according to tracer
- the importing of multiple PET volumes.
- extracting individual PET frames
- co-registration with MRI
- saving PET volumes in Brainstorm format
- database CRUD for referencing new PET volume in database
- GUI update with new imported PET
- Visualization of imported PET onto the subject MRI

#### #33: Detect PET File Format (Functional)
Convert PET volume to NIFTI1 if not already in NIFTI1

#### #38: Extract the frame count from PET file (Functional)

#### #43: Save imported PET in Brainstorm format (Functional)

#### #44: Reference the newly imported PET file into the Brainstorm database (Functional)

#### #45: Update the GUI tree with the newly imported PET file (Functional)

##### #36: Naming of PET file in GUI must include tracer information (Functional)

##### #40: Naming of PET file in GUI must include the frame count (Functional)
Frame count will be included in brackets and shown in the GUI tree.

#### #46: Pre-process PET frames (Container)
If imported PET volume contain multiple frames,
1. Align frames to a reference frame
2. Take the voxel-wise mean across the frames
3. Co-register the averaged, aligned PET to subject MRI

##### #47: Align each frame to a reference frame (Functional)

##### #48: Take the voxel-wise mean across the aligned frames (Functional)

##### #49: Co-register the averaged, aligned PET to subject MRI (Functional)

#### #51: Visualize the imported and pre-processed PET volume (Container)
The imported and pre-processed PET data will be visualized in the MRI viewer.

##### #52: Overlay pre-processed PET onto the subject MRI (Functional)

###### #78: Define display setting for smoothing, color scheme and intensity normalization. (Functional)

##### #77: Launch MRI viewer (Functional)

#### #88: Import processed PET (Functional)
A set of functions or code blocks for importing PET and PET derivatives from pipelines implemented outside of Brainstorm, in Brainsuite or Freesurfer.

#### #89: Parse user inputs (Functional)
This task is responsible for checking and assigning default values to function inputs if they are not provided.

##### #90: Default to 'ALL' if not input is provided (Functional)
'.

##### #91: Default to 'ALL' if partial input is provided (Functional)

##### #92: Use all inputs if all inputs are provided (Functional)

#### #98: Load PET (Functional)

#### #99: Import Brainstorm Format (Functional)

#### #100: Import Nifti Format (Functional)

#### #101: Import DICOM Format (Functional)

#### #102: Import MGH Format (Functional)

#### #107: Import PET BIDS (Container)

##### #108: Modify process_import_bids to look for PET (Functional)

##### #109: Modify bst_jsonencode to read PET-BIDS (Functional)

#### #113: Unzip PET (Functional)

#### #115: Get global variables (Functional)

### #10: Process PET (Container)
PET processing will be performed through pipelines either in Brainsuite or Freesurfer, depending on user selection.
The processing pipelines, whether Brainsuite or Freesurfer, will feature identical processing steps, culminating in the projection of SUVR data onto the subject's reconstructed surface.
The surface projection of SUVR data will be imported back into Brainstorm for analysis and co-visualization with MEG.

#### #11: Export PET to temp folder for Freesurfer (Functional)

##### #67: Pass selected PET volume to Brainsuite or Freesurfer (Functional)

##### #68: Pass subject T1 MRI to Brainsuite or Freesurfer (Functional)

#### #12: SUVR Calculation (Functional)

#### #13: Partial Volume Correction (Functional)

#### #66: Parse user inputs from PET processing GUI (Functional)

#### #69: SUVR Surface Projection (Functional)

#### #70: Import SUVR surface projection into Brainstorm (Functional)

#### #133: Export anatomical data to temp folder for Freesurfer (Functional)

### #14: Visualize PET (Container)

#### #15: Overview (Informational)
Visualization functions will consist of volume and surface-based plotting of PET data. The objective is to allow the user to co-visualize PET data together with MRI (for volumes) and MEG (for surfaces). The visualization functions will include options for smoothing and renormalization of PET data.

### #123: Pre-process PET (Functional)

### #126: Export PET (Functional)

#### #106: Export PET to nifti (Functional)
out_pet_nii

#### #134: Export PET to bst format (Functional)

##### #135: Save imported PET onto hard drive in .mat format (Functional)

#### #137: Integrate imported PET into protocol (Functional)

## #5: GUI Requirements (Container)
The current Brainstorm GUI will be extended to facilitate three core steps in PET processing:
1. Importing PET data
2. Processing PET data
3. Co-analyzing PET and MEG data

### #6: Add "Import PET" as a GUI component (Functional)
Add an "Import PET" item in the subject contextual menu in the Brainstorm tree. The GUI item implement the function "import_pet.m".
Concept:
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
### #53: GUI for PET processing (Container)

### #54: Dropdown for selecting Brainsuite or Freesurfer (Functional)

### #55: Dropdown or selection list for SUVR reference region (Functional)

### #56: Check box for partial volume correction (Functional)

### #57: Disabled by default, unless PVC check box is on (Functional)

### #58: Default PSF value is 2.8 (full width at half maximum) (Functional)

### #59: Check box for parallel processing (Functional)
Default is off.

### #60: Field for number of threads for parallel processing (Functional)

### #61: Default is 1. (Functional)

### #62: Disabled by default, unless check box for parallel processing is on. (Functional)

### #63: Default is off (Functional)

### #64: Field for point spread function value (Functional)

### #65: Default is off (Functional)

### #73: Add PET as a new data type (Container)
PET will be included as a distinct data type in the Brainstorm tree.
This will feature a PET icon and naming conventions, PET-specific contextual menu and a dialogue box or GUI for processing PET data in Brainsuite and Freesurfer.
The PET data label to the right of the icon must include:
- the name of the tracer
- the number of frames in the PET volume in brackets

### #81: Add a PET popup to the PET data type (Functional)
Based on the Anatomy popup, the PET popup will have PET-related items:
1. Display --> Overlay PET on MRI
2. Alight PET Frames
3. Calculate SUVR
4. Project SUVR to surface
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
#### #82: Display (Functional)
The "Display" GUI items will be identical to the current MRI display items (image below) but will call PET-specific display code from PET visualization functions.
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
#### #83: Register PET to MRI (Functional)

#### #85: Align PET Frames (Functional)

#### #86: Calculate SUVR (Functional)
Launches the process_suvr_pet GUI and calls process_suvr_pet function.

##### #72: Add "Process PET" as a GUI component (Functional)
The "Calculate SUVR" popup launches a GUI for collecting user-provided parameters for calculating SUVR from PET data.
Conceptual design for PET processing GUI
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
#### #87: Project SUVR to surface (Functional)

### #114: Select PET file in local dataset (Functional)

### #139: Java Bst Requirements (Container)

#### #75: Add a new icon for PET data (Functional)

#### #140 (Functional)

## #16: Non-functional Requirements (Container)

### #7: Feedback and notifications (Informational)
GUI should provide feedback for each action (e.g., “Dataset successfully imported,” “PET File Imported”) etc.

### #18: Error handling (Informational)
Error handling will be implemented to guide users in case of incorrect inputs or processing failures.

### #19: Contextual tool tips (Informational)
Contextual tooltips will be provided to explain the use of each feature.

### #20: Compatibility (Informational)
The PET toolkit must be fully compatible with the existing Brainstorm architecture and make use of supported MATLAB functions.
The extension will support all major operating systems that Brainstorm supports (Windows, macOS, Linux).

### #21: Open-source (Informational)

### #22: Intuitive interface (Informational)
The added interfaces will be intuitive and navigation will be integrated with established Brainstorm workflows.
- Keywords: Intuitive

### #23: Performance (Informational)
The PET toolkit will handle data volumes of varying sizes, from small single-session studies to large longitudinal datasets, without significant lag.
Data processing tasks such as MRI-PET registration and PVC should execute efficiently, leveraging multicore processing where available.

#### #24: Memory and processing constraints (Functional)
- The GUI must not introduce performance bottlenecks or interfere with the existing functionalities of Brainstorm.
- The GUI must operate within the memory and processing constraints of common research workstations.

### #25: Maintainability (Informational)
The code should follow Brainstorm’s development standards and be well-documented to allow for easy maintenance and updates.

## #26: Test Requirements (Container)

### #28: Test Cases (Container)

#### #29: Nominal Mode Tests (Container)

#### #30: Tests for invalid conditions (Functional)

### #80: Test Data Requirements (Functional)
Test data will be a multimodal dataset, consisting of MEG, MRI and PET imaging.

## #119: Data Requirements (Container)
This set describes the data organization requirements for the addition of PET data type to the Brainstorm environment. PET and PET-related data stored on the hard drive and maintained in-memory during runtime will have defined conventions such as file labelling of PET data in Brainstorm format, directory paths, runtime data PET data structures allocated to GlobalData and BIDS requirements for multimodal integration.

### #120: Store PET metadata in database (Functional)

#### #96: Add PET to default formats (Functional)
Update bst_get to return PetIn as a default format.

#### #97: Add PET File Filters (Functional)
Modify bst_get to add file filters for common PET formats: DICOM, Nifti1, MGH, MNI, Analyze.

#### #116: Reference PET to Subject (Functional)

#### #117: Reference PET to subjectmat (Functional)

### #121: Store PET neuroimaging data in database (Functional)

### #122: Allocate PET to GlobalData (Functional)

### #124: Store imported PET in temporary directory (Functional)

#### #118: Create loadedpet structure for temporary loading (Functional)

### #125: PET data table in SQL database (Functional)

#### #104: Add petmat to SQL database (Functional)

## #127: Service Layer Requirements (Container)

### #128: Save PET database to data repository (Functional)

### #129: Assign PET data to GlobalData (Functional)

### #130: Save PET metadata to database (Functional)

### #131: Get PET from GlobalData (Functional)

### #132: Load PET from data repository (Functional)
